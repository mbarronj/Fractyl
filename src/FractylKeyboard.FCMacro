# pyright: reportMissingImports=false
# -*- coding: utf-8 -*-
# Fractyl Keyboard generator: 
# Like its earlier cousins, generates a tented,
# curved, ergonomic keyboard. Similar to Dactyl-Manuform.
# Relevant differences: This tool specfically generates freecad geometry 
# primatives, meaning all of the geometry is natively-editable in FreeCAD. 
# Not that it's robust - edit the resulting CAD file at your own risk.
# Also, this tool is intended to work with a measurement of a hand - your own,
# or some generic model. It does not generate a circular curve, rather a specific
# curve generated by articulation of finger joints.
# There are jupyter iPython notebooks related to generating hand measurement data
# using webcams and MediaPipe, also a work-in-progress

__Name__ = 'Fractyl'
__Comment__ = 'Creates Custom-Fitted Ergonomic Keyboards'
__Author__ = 'mbarronj'
__Version__ = '0.0.1'
__Date__ = '2024-01-16'
__License__ = 'LGPL-3.0-or-later'
__Web__ = 'http://authintelligence.com'
__Wiki__ = ''
__Icon__ = ''
__Help__ = 'Try it out and play with it. It should be self explanatory'
__Status__ = 'Alpha'
__Requires__ = 'FreeCAD >= v0.20'
__Communication__ = ''
__Files__ = 'Fractyl'
import importlib # for reloading modules during test
# for working with individual modules, in the FreeCAD Python console:
# import importlib
# pth = App.getUserAppDataDir()
# mcr = pth+macro_file_name
# reload(mcr)
# or
#pth = r"C:\Users\mbarr\OneDrive\Documents\01. Projects\03_SW_Dev\Fractyl\src\Fractyl"
#filename = "FractylKeyboard.FCMacro" # "Mesh_From_Points.py"
#exec(open(pth + "\\" + filename).read())

import FreeCAD as App
import FreeCADGui as Gui

# Ensure we have a new document before attempting any further import, if needed
try:
    doc = App.activeDocument()
except Exception as e:
    App.Console.PrintMessage("Fractyl - no open file. Creating new file\n")
    #if doc is None:
    doc = App.newDocument()


#from Fractyl import dmkb_keyplate
import Fractyl
#importlib.reload(Fractyl)

keyrows = ['top','middle','bottom']
fingers = ['point', 'index', 'ring', 'pinky']


try:
    App.Console.PrintMessage("Fractyl Keyboard Generation Macro Running . . . \n")
    App.Console.PrintMessage("Reading Hand Measurement Data\n")
    finger_data = Fractyl.readHandData()

    if finger_data is not None:
        Fractyl.create_Rotated_kps(finger_data)
    else:
        App.Console.PrintMessage("ERROR: Could not create key plates\n")
        raise Exception("Fractyl Macro Error: No Keyplates Generated")

    App.Console.PrintMessage("Filling web between keyplates\n")
    Fractyl.FillWeb(keyrows,fingers)

    App.Console.PrintMessage("Filling gap between key Columns\n")
    Fractyl.fillColumnMesh(fingers)

    App.Console.PrintMessage("Fusing Objects\n")
    Fractyl.Fuse_Objects()
    Fractyl.Rotate_Object()
    
    App.Console.PrintMessage("Creating Thumb Key Plates\n")
    Fractyl.create_thumbpad()
    
    Gui.SendMsgToActiveView("ViewFit")
except Exception as e:
    App.Console.PrintMessage("Fractyl did not complete generation, exiting\n")
    App.Console.PrintMessage(f"{e}")
